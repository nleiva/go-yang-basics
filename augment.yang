module network-device-extensions {
  namespace "urn:example:network:extensions";
  prefix "net-ext";

  import network-device { prefix net; }

  augment "/net:interface" {
    leaf status {
      description "Interface operational status";
      type union {
        type enumeration {
          enum up {
            description "Interface is operational";
          }
          enum down {
            description "Interface is not operational";
          }
          enum testing {
            description "Interface is in testing mode";
          }
        }
        type string {
          pattern "maintenance-.*";
        }
      }
    }
    
    leaf bandwidth {
      type uint32 {
        range "1..10000";
      }
      units "Mbps";
      description "Interface bandwidth in Megabits per second";
    }
  }
}
