module network-device-restrictions {
  namespace "urn:example:network:restrictions";
  prefix "net-restrict";

  import network-device { prefix net; }

  deviation /net:interface/net:name {
    deviate replace {
      type string {
        pattern 'eth[0-9]+|wlan[0-9]+';
      }
    }
    description "Restrict interface names to ethernet (ethX) or wireless (wlanX) patterns";
  }
}
