module network-device {
  namespace "urn:example:network";
  prefix "net";

  typedef priority-level {
    type uint8 {
      range "1..5 | 10..15";
    }
    description "Network priority levels: 1-5 (low priority) or 10-15 (high priority)";
  }

  container interface {
    description "Network interface configuration";
    
    leaf name {
      type string;
      description "Interface name (e.g., eth0, wlan0)";
    }
    
    leaf mtu {
      type uint16 {
        range "68..9216";
      }
      description "Maximum Transmission Unit in bytes";
    }
    
    leaf priority {
      type priority-level;
      description "Interface priority level";
    }
  }
}
